(defun c:haws-chm (/ ss dc dl dlt ec)
(haws-core-init 172)
  (prompt "Pick entities to change: ")
  (setq ss (ssget)
    ec (entsel "Entity to match: ")       dc (cdr (assoc 62 (entget(car ec))))
    dl (cdr (assoc 8 (entget (car ec))))  dlt (cdr (assoc 6 (entget(car ec))))
  )
  (if (not dlt)(setq dlt "BYLAYER"))
  (if (not dc)(setq dc "BYLAYER"))
  (vl-cmdf "._CHANGE" ss "" "_P" "_LT" dlt "_LA" dl "_C" dc "" )
  (prompt "Entities changed to:.....\n ")
  (list "Layer:..>>" dl "Color:..>>" dc "Ltype:..>>" dlt)
)
