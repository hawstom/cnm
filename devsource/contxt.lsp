;Written by Thomas Gail Haws
(defun c:haws-contxt (/ txtht txtstr inspt rot)
  (haws-core-init 212)
  (haws-vsave '("cmdecho"))
  (setq txtstr (getstring "\nContour text:"))
  (haws-setlayr "CONTLBL")
  (setq inspt (getpoint "\nMiddle point:") rot (getangle inspt " Rotation: "))
  (haws-mktext "m" inspt nil rot txtstr)
  (haws-vrstor)(haws-core-restore)(princ)
)
