;QUICK DTEXT COMMANDS
;Written by Thomas Gail Haws
(defun haws-qdtext (ts / pt1)
  (setq pt1 (getpoint "\nStart point: "))
  (prompt "\nText: ")
  (vl-cmdf "._dtext" pt1 (* ts (haws-dwgscale)) "0")
)
(defun c:haws-l80  ()
(haws-core-init 294) (haws-qdtext 0.08 ))
(defun c:haws-l100 ()
(haws-core-init 295) (haws-qdtext 0.10 ))
(defun c:haws-l120 ()
(haws-core-init 296) (haws-qdtext 0.12 ))
(defun c:haws-l140 ()
(haws-core-init 297) (haws-qdtext 0.14 ))
(defun c:haws-l175 ()
(haws-core-init 298) (haws-qdtext 0.175))
(defun c:haws-l200 ()
(haws-core-init 299) (haws-qdtext 0.20 ))
(defun c:haws-l240 ()
(haws-core-init 300) (haws-qdtext 0.24 ))
(defun c:haws-l290 ()
(haws-core-init 301) (haws-qdtext 0.29 ))
(defun c:haws-l350 ()
(haws-core-init 302) (haws-qdtext 0.35 ))
(defun c:haws-l500 ()
(haws-core-init 303) (haws-qdtext 0.50 ))
;END QUICK DTEXT
