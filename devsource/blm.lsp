(defun c:haws-xda ()
(haws-core-init 5)(vl-cmdf "._XREF" "D" "*")(princ))
(defun c:haws-xra ()
(haws-core-init 6)(vl-cmdf "._XREF" "R" "*")(princ))
;;--------------------------END ONE LINERS-------------------------
;;--------------------------ONE LINERS-------------------------
