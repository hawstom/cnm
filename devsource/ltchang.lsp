;(C) Copyright 1997 by Thomas Gail Haws
(defun c:haws-ltc (/ ss dl ec)
(haws-core-init 248)
  (setq ec (entsel "Pick Layer to Change Entities to Continuous:"))
  (setq dl (cdr (assoc 8 (entget (car ec)))))
  (setq ss (ssget "X" (list (cons '8 dl))))
  (vl-cmdf "change" ss "" "p" "lt" "continuous" "")
)
(defun c:haws-ltb (/ ss dl ec)
(haws-core-init 249)
  (setq ec (entsel "Pick Layer to Change Entities to Bylayer:"))
  (setq dl (cdr (assoc 8 (entget (car ec)))))
  (setq ss (ssget "X" (list (cons '8 dl))))
  (vl-cmdf "._change" ss "" "_p" "_lt" "bylayer" "")
)

(defun c:haws-lth (/ ss)
(haws-core-init 250)
  (prompt "\nEntities to Change to Linetype Hidden:")
  (setq ss (ssget))
  (vl-cmdf "._change" ss "" "_p" "_lt" "hidden" "")
)
