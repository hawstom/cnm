;Leaders with special heads
;Written by Craig Hendricks and Thomas Gail Haws
(defun c:haws-loop ()
(haws-core-init 242) (vl-cmdf "._insert" "dimloop")(vl-cmdf)(haws-leader "dimloop"))
(defun c:haws-tilde ()
(haws-core-init 243) (haws-leader "Integral"))
(defun c:haws-dot ()
(haws-core-init 244) (haws-leader "DotSmall"))
(defun c:haws-none ()(haws-leader "None"))
(defun haws-leader (dimblk / dbold pt txt)
  (haws-core-init 245)
  (vl-cmdf "._Dim1" "_Dimldrblk" dimblk)
  (vl-cmdf "._Leader")
  (haws-vrstor)(haws-core-restore)(princ)
)
