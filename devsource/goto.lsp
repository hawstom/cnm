(defun c:haws-goto ( / i ss1 en ept vwctr opt crad)
  (haws-core-init 223)
  (haws-vsave '("osmode"))
  (setvar "osmode" 0)
  (setq i 0 ss1 (ssget))
  (while (setq en (if ss1(ssname ss1 i)nil))
    (setq ept (trans(cdr (assoc 10 (entget en))) en 1) vwctr (getvar "viewctr"))
    (vl-cmdf "._pan" ept vwctr)
    (initget "Save Circle In Out eXit Previous Next")
    (setq opt (getkword "\n[Save view/Circle area/zoom In/zoom Out/eXit/Previous/Next] <Next>: "))
    (cond
      ( (= opt "Save")
        (setq vn(getstring "\nNew view name: "))
        (vl-cmdf "._view" "_s" vn)
      )
      ( (= opt "Circle")
        (if (not crad) (setq crad (getreal "\nCircle radius: ")))
        (vl-cmdf "._circle" ept crad)
      )
      ( (= opt "In") (vl-cmdf "._zoom" "2.0x"))
      ( (= opt "Out") (vl-cmdf "._zoom" "0.5x"))
      ( (= opt "Previous") (setq i (- i 1)))
      ( (or (not opt)(= opt "Next")) (setq i (1+ i)))
      ( t (setq i -2))
  ) )
  (haws-vrstor)(haws-core-restore)(princ)
)
