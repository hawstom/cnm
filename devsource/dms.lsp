;;--------------------------ONE LINERS-------------------------
(defun c:haws-d1 ()
(haws-core-init 15)(haws-vtog '("DIMSE1")))
(defun c:haws-d2 ()
(haws-core-init 16)(haws-vtog '("DIMSE2")))
(defun c:haws-dp ()
(haws-core-init 17)(vl-cmdf "DIM1" "DIMPOST")(princ))
(defun c:haws-du ()
(haws-core-init 18)(vl-cmdf "DIM1" "UPDATE")(princ))
(defun c:haws-dv ()
(haws-core-init 19)(vl-cmdf "DIM1" "VER")(princ))
(defun c:haws-ht ()
(haws-core-init 20)(vl-cmdf "DIM1" "HOMETEXT")(princ))
(defun c:haws-te ()
(haws-core-init 21)(vl-cmdf "DIM1" "TEDIT")(princ))
(defun c:haws-dimtixtoggle ()
(haws-core-init 22)(haws-vtog '("DIMTIX")))
;;--------------------------END ONE LINERS-------------------------
