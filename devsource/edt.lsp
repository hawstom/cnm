;;--------------------------ONE LINERS-------------------------
(defun c:haws-bf ()
(haws-core-init 28)(vl-cmdf "._BREAK" pause "F")(princ))
(defun c:haws-copy ()
(haws-core-init 29)(vl-cmdf "._COPY" (ssget) "" "M")(princ))
(defun c:haws-cb ()
(haws-core-init 30) (vl-cmdf "._copybase" "0,0") (princ))
(defun c:haws-mp ()
(haws-core-init 31) (vl-cmdf "._MOVE" "P")(princ))
(defun c:haws-pj ()
(haws-core-init 32) (vl-cmdf "._pedit" "m" (ssget) "" "_y" "_join" "0.005" "")(princ))
(defun c:haws-r1 ()
(haws-core-init 33) (vl-cmdf "._ROTATE" (ssget) "" pause "180") (princ))
(defun c:haws-r2 ()
(haws-core-init 34) (vl-cmdf "._ROTATE" (ssget) "" pause "270") (princ))
(defun c:haws-r4 ()
(haws-core-init 35) (vl-cmdf "._ROTATE" (ssget) "" pause "45") (princ))
(defun c:haws-r9 ()
(haws-core-init 36) (vl-cmdf "._ROTATE" (ssget) "" pause "90") (princ))
(defun c:haws-s  ()
(haws-core-init 37)(vl-cmdf "._STRETCH" "C")(princ))
(defun c:haws-ub ()
(haws-core-init 38)(vl-cmdf "._UNDO" "BACK")(princ))
(defun c:haws-um ()
(haws-core-init 39)(vl-cmdf "._UNDO" "M")(princ))
(defun c:haws-vb ()
(haws-core-init 40) (vl-cmdf "._pasteclip" "0,0") (princ))
;;--------------------------END ONE LINERS-------------------------
