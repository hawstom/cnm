(defun c:haws-aee ()
(haws-core-init 155)
  (prompt "\nSelect object: ")
  (vl-cmdf "._AREA" "_E" pause)
  (princ "Area=")
  (princ (getvar "AREA"))
  (princ "  Length=")
  (princ (getvar "PERIMETER"))
  (princ "  Area in acres=")
  (princ (/ (getvar "AREA") 43560))
  (princ)
)
