(defun c:haws-qs14 ()
(haws-core-init 94) (vl-cmdf "._saveas" "r14" (haws-getdnpath) "y"))
(defun c:haws-qs2000 ()
(haws-core-init 95) (vl-cmdf "._saveas" "2000" (haws-getdnpath) "y"))
(defun c:haws-qs2004 ()
(haws-core-init 96) (vl-cmdf "._saveas" "2004" (haws-getdnpath) "y"))
