;;--------------------------ONE LINERS-------------------------
(defun c:haws-2x ()
(haws-core-init 140)(vl-cmdf "'ZOOM" ".2X")(princ))
(defun c:haws-5x ()
(haws-core-init 141)(vl-cmdf "'ZOOM" ".5X")(princ))
(defun c:haws-9x ()
(haws-core-init 142)(vl-cmdf "'ZOOM" ".9X")(princ))
(defun c:haws-twz()
(haws-core-init 143)(c:haws-tw) (vl-cmdf "._ucs" "_view")(princ))
(defun c:haws-x2 ()
(haws-core-init 144)(vl-cmdf "'ZOOM" "2X")(princ))
(defun c:haws-zw ()
(haws-core-init 145)(vl-cmdf "'ZOOM" "W")(princ))
(defun c:haws-z0 ()
(haws-core-init 146)(vl-cmdf "'ZOOM" "W" "0,0" "36,24")(princ))
(defun c:haws-za ()
(haws-core-init 147)(vl-cmdf "'ZOOM" "A")(princ))
(defun c:haws-ze ()
(haws-core-init 148)(vl-cmdf "'ZOOM" "E")(princ))
(defun c:haws-zi ()
(haws-core-init 149)(vl-cmdf "'ZOOM" "1.5X")(princ))
(defun c:haws-zo ()
(haws-core-init 150)(vl-cmdf "'ZOOM" "0.5X")(princ))
(defun c:haws-zv ()
(haws-core-init 151)(vl-cmdf "'ZOOM" "V")(princ))
(defun c:haws-zz ()
(haws-core-init 152)(vl-cmdf "'ZOOM" "P")(princ))
;;--------------------------END ONE LINERS-------------------------
