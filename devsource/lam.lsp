(defun c:haws-l0 ()(haws-core-init 73)(vl-cmdf "._LAYER" "T" "0" "S" "0" "")(princ))
;;(DEFUN c:haws-LK0 () (haws-core-init 74)(vl-cmdf "._LAYER" "LOCK" "0" "")(PRINC))
(defun c:haws-lka ()(haws-core-init 75)(vl-cmdf "._LAYER" "LO" "*" "")(princ))
(defun c:haws-lki ()(haws-core-init 76)(vl-cmdf "._LAYISO" "_Settings" "_Lock" "")(princ))
(defun c:haws-ofi ()(haws-core-init 77)(vl-cmdf "._LAYISO" "_Settings" "_Off" "_Off")(princ))
(defun c:haws-ula ()(haws-core-init 78)(vl-cmdf "._LAYER" "U" "*" "")(princ))
;;--------------------------END ONE LINERS-------------------------
