;;--------------------------ONE LINERS-------------------------
(defun c:haws-0 ()
(haws-core-init 100)(setvar "TILEMODE" 0)(princ))
(defun c:haws-1 ()
(haws-core-init 101)(setvar "TILEMODE" 1)(princ))
(defun c:haws-aa ()
(haws-core-init 102)(vl-cmdf "SNAPANG" 0 "SNAPANG")(princ))
(defun c:haws-adt ()
(haws-core-init 103)(haws-vtog '("ATTDIA")))
(defun c:haws-cet ()
(haws-core-init 104)(haws-vtog '("CMDECHO")))
(defun c:haws-cmd ()
(haws-core-init 105)(haws-vtog '("CMDDIA")))
(defun c:haws-dia ()
(haws-core-init 106)(haws-vtog '("FILEDIA" "CMDDIA" "ATTDIA")))
(defun c:haws-fdt ()
(haws-core-init 107)(haws-vtog '("FILEDIA")))
(defun c:haws-mbt ()
(haws-core-init 108)(haws-vtog '("MENUBAR")))
(defun c:haws-qt ()
(haws-core-init 109)(haws-vtog '("QTEXTmoDE")))
(defun c:haws-il ()
(haws-core-init 110)(vl-cmdf "SNAP""S""I" "" "SNAP""OF" "ISOPLANE" "L")(princ))
(defun c:haws-io ()
(haws-core-init 111)(vl-cmdf "SNAP""S""S" "" "SNAP""OF")(princ))
(defun c:haws-ir ()
(haws-core-init 112)(vl-cmdf "SNAP""S""I" "" "SNAP""OF" "ISOPLANE" "R")(princ))
(defun c:haws-it ()
(haws-core-init 113)(vl-cmdf "SNAP""S""I" "" "SNAP""OF" "ISOPLANE" "T")(princ))
(defun c:haws-llt ( / eold)
(haws-core-init 114)(setq eold (getvar "EXPERT"))(setvar "EXPERT" 5)(vl-cmdf "LINETYPE" "L" "*" "" "")(setvar "EXPERT" eold)(princ))
(defun c:haws-mvl ()
(haws-core-init 115) (vl-cmdf "._mview" "lock" "on" pause "")(princ))
(defun c:haws-mvu ()
(haws-core-init 116) (vl-cmdf "._mview" "lock" "off" pause "")(princ))
(defun c:haws-ose ()
(haws-core-init 117)(vl-cmdf "OSNAP" "END")(princ))
(defun c:haws-osi ()
(haws-core-init 118)(vl-cmdf "OSNAP" "INT")(princ))
(defun c:haws-osm ()
(haws-core-init 119)(vl-cmdf "OSNAP" "MID")(princ))
(defun c:haws-osn ()
(haws-core-init 120)(vl-cmdf "OSNAP" "NON")(princ))
(defun c:haws-pslt ()
(haws-core-init 121)(haws-vtog '("PSLTSCALE")))
(defun c:haws-proto ()
(haws-core-init 122)(vl-cmdf "INSERT" "*PROTO" "0,0" "" "")(princ))
(defun c:haws-protox ()
(haws-core-init 123)(vl-cmdf "INSERT" "*PROTOX" "0,0" "" "")(princ))
(defun c:haws-rga ()
(haws-core-init 124)(haws-vtog '("REGENMODE")))
(defun c:haws-uf ()
(haws-core-init 125)(haws-vtog '("UCSFOLLOW")))
(defun c:haws-uf0 ()
(haws-core-init 126)(princ "\nType UF to toggle UCSFOLLOW")(princ))
(defun c:haws-uf1 ()
(haws-core-init 127)(princ "\nType UF to toggle UCSFOLLOW")(princ))
(defun c:haws-vsr ()
(haws-core-init 128)(haws-vtog '("VISRETAIN")))
;;--------------------------END ONE LINERS-------------------------
