;Units setting routines
;Written by Thomas Gail Haws
(defun haws-unitset (lu lp au dau ap dp uprmpt)
  (setvar "lunits" lu)
  (setvar "luprec" lp)
  (if (/= (getvar "dimdec") lp)(setvar "dimdec" lp))
  (setvar "aunits" au)
  (setvar "auprec" ap)
  (setvar "dimaunit" dau)
  (setvar "dimadec" ap)
  (setvar "dimpost" dp)
  (prompt "\nUnits now set to " )
  (princ uprmpt)
  (princ)
)
(defun c:haws-u0 (/)
(haws-core-init 320)(haws-unitset 2 0 0 0 0 "'" "0 decimal places."))
(defun c:haws-u1 (/)
(haws-core-init 321)(haws-unitset 2 1 0 0 1 "'" "1 decimal place."))
(defun c:haws-u2 (/)
(haws-core-init 322)(haws-unitset 2 2 0 0 2 "'" "2 decimal places."))
(defun c:haws-u3 (/)
(haws-core-init 323)(haws-unitset 2 3 0 0 3 "'" "3 decimal places."))
(defun c:haws-u8 (/)
(haws-core-init 324)(haws-unitset 2 8 0 0 8 "'" "8 decimal places."))
(defun c:haws-us (/)
(haws-core-init 325)(haws-unitset 2 2 4 3 4 "'" "2 decimal places and surveyor's angles."))
;end unit setting routines
