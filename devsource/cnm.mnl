(princ "\nAutoCAD is automatically loading cnm.mnl from the same folder as cnm.cuix ...")
(apply
  '(lambda (/ fname)
    (cond
      (haws-mklayr (princ "\nSkipping CNMLoader.lsp.  Already loaded."))
      ((not (setq fname (findfile "cnmloader.lsp"))) (princ "\nCNM cannot load because cnmloader.lsp is not in the AutoCAD Support Files Search Path."))
      (t (princ (strcat "\nLoading " fname " from cnm.mnl."))(load fname))
    )
  )
  nil
)
(princ "\ncnm.mnl loaded.")
(princ)
