;; EE.LSP
;; combined dialogue editor for
;; blocks, attdefs, text, and dimensions.

(defun c:haws-ee ()
  (haws-core-init 27)
  (haws-editall nil)
  (haws-core-restore)
)
(defun haws-editall  (cnm-p / e etype set1 obj1 )
  (VL-CMDF "._undo" "_group")
  (PROMPT "\nText Editor:")
  (SETQ SET1 (SSGET))
  (WHILE (AND SET1
    (SETQ OBJ1 (SSNAME SET1 0)))
    (SETQ E (ENTGET OBJ1) ETYPE (cdr(assoc 0 e)))
    (REDRAW OBJ1 3)
    (cond
      ( cnm-p
        (HCNM_EDIT_BUBBLE OBJ1)
      )
      ( (AND (= etype "INSERT") (CDR (ASSOC 66 E)))
        (VL-CMDF "._TEXTEDIT" OBJ1)
      )
      ( (= etype "ATTDEF")
        (VL-CMDF "._TEXTEDIT" OBJ1 "")
      )
      ( (= etype "TEXT")
        (VL-CMDF "._TEXTEDIT" OBJ1 "")
      )
      ( (= etype "MTEXT")
        (VL-CMDF "._TEXTEDIT" OBJ1 "")
      )
      ( (= etype "DIMENSION")
        (VL-CMDF "._TEXTEDIT" OBJ1 "")
    ) )
    (REDRAW OBJ1 4)
    (IF (/= OBJ1 NIL)(SSDEL OBJ1 SET1))
  )
  (VL-CMDF "._undo" "_end")
)
