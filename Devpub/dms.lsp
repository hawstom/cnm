;;--------------------------ONE LINERS-------------------------
(DEFUN c:haws-D1 ()
(haws-core-init 15)(HAWS-VTOG '("DIMSE1")))
(DEFUN c:haws-D2 ()
(haws-core-init 16)(HAWS-VTOG '("DIMSE2")))
(DEFUN c:haws-DP ()
(haws-core-init 17)(COMMAND "DIM1" "DIMPOST")(PRINC))
(DEFUN c:haws-DU ()
(haws-core-init 18)(COMMAND "DIM1" "UPDATE")(PRINC))
(DEFUN c:haws-DV ()
(haws-core-init 19)(COMMAND "DIM1" "VER")(PRINC))
(DEFUN c:haws-HT ()
(haws-core-init 20)(COMMAND "DIM1" "HOMETEXT")(PRINC))
(DEFUN c:haws-TE ()
(haws-core-init 21)(COMMAND "DIM1" "TEDIT")(PRINC))
(DEFUN c:haws-dimtixtoggle ()
(haws-core-init 22)(HAWS-VTOG '("DIMTIX")))
;;--------------------------END ONE LINERS-------------------------
