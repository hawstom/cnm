(Defun AH (/ P1 P2 P3)
  (prompt "\n @ Half")
  (initget 17)(Setq P1 (Getpoint "\nEnter first point: "))
  (initget 17)(Setq P2 (Getpoint "\nEnter second point: "))
  (Setq P3 (list (/ (+ (car p1) (car p2)) 2)
      (/ (+ (cadr p1) (cadr p2)) 2)
      (/ (+ (caddr p1) (caddr p2)) 2)
  )  )
  (Command P3)(Princ)
)
