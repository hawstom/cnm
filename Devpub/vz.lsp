;;--------------------------ONE LINERS-------------------------
(DEFUN c:haws-2X ()
(haws-core-init 140)(COMMAND "'ZOOM" ".2X")(PRINC))
(DEFUN c:haws-5X ()
(haws-core-init 141)(COMMAND "'ZOOM" ".5X")(PRINC))
(DEFUN c:haws-9X ()
(haws-core-init 142)(COMMAND "'ZOOM" ".9X")(PRINC))
(defun c:haws-twz()
(haws-core-init 143)(c:haws-tw) (command "._ucs" "_view")(PRINC))
(DEFUN c:haws-X2 ()
(haws-core-init 144)(COMMAND "'ZOOM" "2X")(PRINC))
(DEFUN c:haws-ZW ()
(haws-core-init 145)(COMMAND "'ZOOM" "W")(PRINC))
(DEFUN c:haws-Z0 ()
(haws-core-init 146)(COMMAND "'ZOOM" "W" "0,0" "36,24")(PRINC))
(DEFUN c:haws-ZA ()
(haws-core-init 147)(COMMAND "'ZOOM" "A")(PRINC))
(DEFUN c:haws-ZE ()
(haws-core-init 148)(COMMAND "'ZOOM" "E")(PRINC))
(DEFUN c:haws-ZI ()
(haws-core-init 149)(COMMAND "'ZOOM" "1.5X")(PRINC))
(DEFUN c:haws-ZO ()
(haws-core-init 150)(COMMAND "'ZOOM" "0.5X")(PRINC))
(DEFUN c:haws-ZV ()
(haws-core-init 151)(COMMAND "'ZOOM" "V")(PRINC))
(DEFUN c:haws-ZZ ()
(haws-core-init 152)(COMMAND "'ZOOM" "P")(PRINC))
;;--------------------------END ONE LINERS-------------------------
