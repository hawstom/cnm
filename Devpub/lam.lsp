(DEFUN c:haws-L0 ()(haws-core-init 73)(vl-cmdf "._LAYER" "T" "0" "S" "0" "")(PRINC))
;;(DEFUN c:haws-LK0 () (haws-core-init 74)(vl-cmdf "._LAYER" "LOCK" "0" "")(PRINC))
(DEFUN c:haws-LKA ()(haws-core-init 75)(vl-cmdf "._LAYER" "LO" "*" "")(PRINC))
(DEFUN c:haws-LKI ()(haws-core-init 76)(vl-cmdf "._LAYISO" "_Settings" "_Lock" "")(PRINC))
(DEFUN c:haws-OFI ()(haws-core-init 77)(vl-cmdf "._LAYISO" "_Settings" "_Off" "_Off")(PRINC))
(DEFUN c:haws-ULA ()(haws-core-init 78)(vl-cmdf "._LAYER" "U" "*" "")(PRINC))
;;--------------------------END ONE LINERS-------------------------
