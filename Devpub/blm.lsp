(DEFUN c:haws-XDA ()
(haws-core-init 5)(COMMAND "._XREF" "D" "*")(PRINC))
(DEFUN c:haws-XRA ()
(haws-core-init 6)(COMMAND "._XREF" "R" "*")(PRINC))
;;--------------------------END ONE LINERS-------------------------
;;--------------------------ONE LINERS-------------------------
