;;--------------------------ONE LINERS-------------------------
(DEFUN c:haws-0 ()
(haws-core-init 100)(SETVAR "TILEMODE" 0)(PRINC))
(DEFUN c:haws-1 ()
(haws-core-init 101)(SETVAR "TILEMODE" 1)(PRINC))
(DEFUN c:haws-AA ()
(haws-core-init 102)(vl-cmdf "SNAPANG" 0 "SNAPANG")(PRINC))
(DEFUN c:haws-ADT ()
(haws-core-init 103)(HAWS-VTOG '("ATTDIA")))
(DEFUN c:haws-CET ()
(haws-core-init 104)(HAWS-VTOG '("CMDECHO")))
(DEFUN c:haws-CMD ()
(haws-core-init 105)(HAWS-VTOG '("CMDDIA")))
(DEFUN c:haws-DIA ()
(haws-core-init 106)(HAWS-VTOG '("FILEDIA" "CMDDIA" "ATTDIA")))
(DEFUN c:haws-FDT ()
(haws-core-init 107)(HAWS-VTOG '("FILEDIA")))
(DEFUN c:haws-MBT ()
(haws-core-init 108)(HAWS-VTOG '("MENUBAR")))
(DEFUN c:haws-QT ()
(haws-core-init 109)(HAWS-VTOG '("QTEXTmoDE")))
(DEFUN c:haws-IL ()
(haws-core-init 110)(vl-cmdf "SNAP""S""I" "" "SNAP""OF" "ISOPLANE" "L")(PRINC))
(DEFUN c:haws-IO ()
(haws-core-init 111)(vl-cmdf "SNAP""S""S" "" "SNAP""OF")(PRINC))
(DEFUN c:haws-IR ()
(haws-core-init 112)(vl-cmdf "SNAP""S""I" "" "SNAP""OF" "ISOPLANE" "R")(PRINC))
(DEFUN c:haws-IT ()
(haws-core-init 113)(vl-cmdf "SNAP""S""I" "" "SNAP""OF" "ISOPLANE" "T")(PRINC))
(DEFUN c:haws-LLT ( / EOLD)
(haws-core-init 114)(SETQ EOLD (GETVAR "EXPERT"))(SETVAR "EXPERT" 5)(vl-cmdf "LINETYPE" "L" "*" "" "")(SETVAR "EXPERT" EOLD)(PRINC))
(DEFUN C:HAWS-MVL ()
(haws-core-init 115) (vl-cmdf "._mview" "lock" "on" PAUSE "")(PRINC))
(DEFUN C:HAWS-MVU ()
(haws-core-init 116) (vl-cmdf "._mview" "lock" "off" PAUSE "")(PRINC))
(DEFUN c:haws-OSE ()
(haws-core-init 117)(vl-cmdf "OSNAP" "END")(PRINC))
(DEFUN c:haws-OSI ()
(haws-core-init 118)(vl-cmdf "OSNAP" "INT")(PRINC))
(DEFUN c:haws-OSM ()
(haws-core-init 119)(vl-cmdf "OSNAP" "MID")(PRINC))
(DEFUN c:haws-OSN ()
(haws-core-init 120)(vl-cmdf "OSNAP" "NON")(PRINC))
(DEFUN c:haws-PSLT ()
(haws-core-init 121)(HAWS-VTOG '("PSLTSCALE")))
(DEFUN c:haws-PROTO ()
(haws-core-init 122)(vl-cmdf "INSERT" "*PROTO" "0,0" "" "")(PRINC))
(DEFUN c:haws-PROTOX ()
(haws-core-init 123)(vl-cmdf "INSERT" "*PROTOX" "0,0" "" "")(PRINC))
(DEFUN c:haws-RGA ()
(haws-core-init 124)(HAWS-VTOG '("REGENMODE")))
(DEFUN c:haws-UF ()
(haws-core-init 125)(HAWS-VTOG '("UCSFOLLOW")))
(DEFUN c:haws-UF0 ()
(haws-core-init 126)(PRINC "\nType UF to toggle UCSFOLLOW")(PRINC))
(DEFUN c:haws-UF1 ()
(haws-core-init 127)(PRINC "\nType UF to toggle UCSFOLLOW")(PRINC))
(DEFUN c:haws-VSR ()
(haws-core-init 128)(HAWS-VTOG '("VISRETAIN")))
;;--------------------------END ONE LINERS-------------------------
