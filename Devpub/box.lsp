;This function will draw a box from two points
(defun c:haws-BX ( / pnt1 pnt2 pnt3 pnt4)
  (graphscr)
  (setq pnt1 (getpoint"\nFirst corner: ") pnt3 (getcorner"Other corner: "pnt1)
    pnt2 (list (car pnt1)(cadr pnt3)) pnt4 (list (car pnt3)(cadr pnt1))
  )
  (command "pline" pnt1 pnt2 pnt3 pnt4 "c")
  (prompt "\nRotation angle ")
  (command "rotate" "l" "" pnt1 pause)
)
