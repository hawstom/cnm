;;;; CNM Test Suite - Validation Functions
;;;; AutoLISP functions for automated test validation
;;;;
;;;; Purpose: Query drawing state and verify test results
;;;; Usage: Loaded by cnm-test.scr during test execution
;;;;
;;;; Created: 2025-11-17
;;;; Status: Active - bubble notes auto-text and updater testing
;;;;
;;;; Architecture:
;;;;   - Test functions query XDATA and attributes
;;;;   - Results annotated on C-ANNO-TEST-RESULTS layer
;;;;   - Report written to test-results/cnm-test-report.md for AI analysis
;;;;   - Timing log written to test-results/cnm-test-run.log
;;;;
;;==============================================================================
;; HELPER FUNCTIONS - DRY utilities for common test patterns
;;==============================================================================
(defun test-find-bubble-by-coord (x y z description / ss en handle)
  ;; Find bubble by insertion point coordinates
  ;; Args:
  ;;   x, y, z - Coordinates (reals)
  ;;   description - String for debug messages (e.g., "TEST 1")
  ;; Returns: Entity name if found, nil otherwise
  ;; Side effects: Sets global variable matching pattern test-bubble-N
  (setq ss (ssget "_X" (list '(0 . "INSERT") (cons 10 (list x y z)))))
  (cond
    ((and ss (> (sslength ss) 0))
     (setq en (ssname ss 0))
     (setq handle (cdr (assoc 5 (entget en))))
     (haws-debug (strcat "\nFound " description " bubble: " handle))
     en
    )
    (t
     (haws-debug (strcat "\nWARNING: " description " bubble not found at ("
                         (rtos x 2 1) ", " (rtos y 2 1) ", " (rtos z 2 1) ")"))
     nil
    )
  )
)
(defun test-modify-mtext-at (x y new-content / ss i e ip found)
  ;; Overwrite DXF group 1 of the MTEXT nearest to (x, y). Used to inject
  ;; format codes and field references into test MTEXT sources without
  ;; requiring a human to edit the drawing. Returns the entity name if
  ;; modified, nil otherwise.
  (setq ss (ssget "_X" '((0 . "MTEXT"))) i -1 found nil)
  (while (and (not found) ss (< (setq i (1+ i)) (sslength ss)))
    (setq e (ssname ss i) ip (cdr (assoc 10 (entget e))))
    (cond
      ((and ip (< (abs (- (car ip) x)) 1.0) (< (abs (- (cadr ip) y)) 1.0))
       (entmod (subst (cons 1 new-content) (assoc 1 (entget e)) (entget e)))
       (setq found e)
      )
    )
  )
  (cond
    (found
     (haws-debug (strcat "\ntest-modify-mtext-at: set DXF 1 of MTEXT near ("
                         (rtos x 2 1) ", " (rtos y 2 1) ")")))
    (t
     (haws-debug (strcat "\nWARNING: test-modify-mtext-at: no MTEXT near ("
                         (rtos x 2 1) ", " (rtos y 2 1) ")")))
  )
  found
)
(defun c:test-setup-layers ( / )
  ;; Create test results layer for MTEXT annotations
  (vl-cmdf "._layer" "_make" "C-ANNO-TEST-RESULTS" "")
  (princ "\nTest suite layers created")
  (princ)
)
(defun c:test-annotate-result (location status message / color x y x-str y-str x-corner y-corner x-corner-str y-corner-str)
  ;; Place MTEXT annotation at specified location with color-coded status
  ;; Args:
  ;;   location - String "x,y" coordinates for annotation
  ;;   status - String "PASS", "FAIL", or "INFO"
  ;;   message - String detailed message text
  ;; Returns: nil (princ suppresses return value)
  ;; [AI: Drawing annotations disabled - safearray errors. Console output only.]
  (princ (strcat "\n[" status "] " message))
  (princ)
)
(defun c:test-generate-summary-mtext ( / pass-count fail-count info-count report-file line resultsdir status-line summary-text)
  ;; Count PASS/FAIL/INFO from report file and generate summary MTEXT
  ;; Returns formatted string for MTEXT command
  (setq pass-count 0)
  (setq fail-count 0)
  (setq info-count 0)
  (setq resultsdir (strcat (getvar "dwgprefix") "test-results"))
  (setq report-file (open (strcat resultsdir "\\cnm-test-report.md") "r"))
  (if report-file
    (progn
      (while (setq line (read-line report-file))
        (if (wcmatch line "*Status:*")
          (progn
            (setq status-line (substr line 13))  ; Skip "**Status:** "
            (cond
              ((wcmatch status-line "PASS*") (setq pass-count (1+ pass-count)))
              ((wcmatch status-line "FAIL*") (setq fail-count (1+ fail-count)))
              ((wcmatch status-line "INFO*") (setq info-count (1+ info-count)))
            )
          )
        )
      )
      (close report-file)
    )
  )
  ;; Generate summary text
  (setq summary-text
    (strcat
      "CNM TEST SUITE - "
      (if (> fail-count 0)
        (strcat (itoa fail-count) " FAILURES DETECTED")
        "ALL TESTS PASSED"
      )
      "\\PResults: "
      (itoa pass-count) " PASS, "
      (itoa fail-count) " FAIL"
      "\\P\\PAuto-Text Validation"
      "\\P- 16 bubble insertions (8 with all 16 auto-text types plus 8 legacy)"
      "\\PKey Notes & QT Tables: Key Notes Table generation validated and QT Table generation validated"
      "\\PCNM-Demo Coverage (CNM Plus Utilities): haws-contvol, haws-ut, haws-mof, haws-lotnum, haws-newpro (profile drafter)"
      "\\P\\PReview test-results/cnm-test-report.md for detailed results."
    )
  )
  (haws-debug (strcat "SUMMARY GENERATED - " (itoa pass-count) " PASS, " (itoa fail-count) " FAIL, " (itoa info-count) " INFO"))
  summary-text
)
(defun test-write-report-header ( / report-file timestamp resultsdir)
  ;; Initialize test-results/cnm-test-report.md with header
  ;; Called at start of test suite execution
  ;; Create test-results subfolder if it doesn't exist
  (setq resultsdir (strcat (getvar "dwgprefix") "test-results"))
  (if (not (vl-file-directory-p resultsdir))
    (vl-mkdir resultsdir)
  )
  (setq report-file (open (strcat resultsdir "\\cnm-test-report.md") "w"))
  (setq timestamp (menucmd "M=$(edtime,$(getvar,date),YYYY-MO-DD HH:MM:SS)"))
  (write-line "# CNM Test Suite Report\n" report-file)
  (write-line (strcat "**Date:** " timestamp "\n") report-file)
  (write-line "**Status:** Running tests...\n" report-file)
  (write-line "---\n" report-file)
  (write-line "## Test Results\n" report-file)
  (close report-file)
  (princ "\nTest report initialized: test-results/cnm-test-report.md")
  (princ)
)
(defun test-write-report-entry (test-name status message / report-file resultsdir)
  ;; Append test result entry to test-results/cnm-test-report.md
  ;; Args:
  ;;   test-name - String name of test (e.g., "TEST 1: Station Auto-Text")
  ;;   status - String "PASS", "FAIL", or "INFO"
  ;;   message - String detailed message
  (setq resultsdir (strcat (getvar "dwgprefix") "test-results"))
  (setq report-file (open (strcat resultsdir "\\cnm-test-report.md") "a"))
  (write-line (strcat "### " test-name "\n") report-file)
  (write-line (strcat "**Status:** " status "\n") report-file)
  (write-line (strcat "**Details:**\n```\n" message "\n```\n") report-file)
  (close report-file)
  (princ)
)
(defun c:test-write-report-summary (/ report-file resultsdir)
  ;; Write summary section to test-results/cnm-test-report.md
  ;; Args:
  ;;   total-count - Total number of tests
  ;; Called at end of test suite execution
  (setq resultsdir (strcat (getvar "dwgprefix") "test-results"))
  (setq report-file (open (strcat resultsdir "\\cnm-test-report.md") "a"))
  (write-line "\n---\n" report-file)
  (write-line "## Summary\n" report-file)
  (write-line "\n**Note:** Review test entries above for PASS/FAIL status.\n" report-file)
  (write-line "Review drawing annotations on C-ANNO-TEST-RESULTS layer for visual results.\n" report-file)
  (close report-file)
  (princ "\nTest report complete: test-results/cnm-test-report.md")
  (princ)
)
(princ "\nCNM Test Suite validation functions loaded")
(princ "\n  Commands: c:test-setup-layers")
(princ "\n  Helpers: test-write-report-*, test-log-*, test-cleanup-*")
(princ "\n  Validators: test-validate-auto-text, test-validate-xdata, test-validate-vptrans-*")
(princ)
;;==============================================================================
;; AUTO-TEXT VALIDATION FUNCTIONS
;;==============================================================================
(defun test-validate-auto-text (ename tag expected-text test-name /
                                lattribs actual-text result status message location
                               )
  ;; Validate bubble attribute text matches expected value
  ;; Args:
  ;;   ename - Entity name of bubble
  ;;   tag - Attribute tag to check (e.g., "NOTETXT1")
  ;;   expected-text - Expected text value (e.g., "STA 3+00.00")
  ;;   test-name - Name for report (e.g., "TEST 1: Station Auto-Text")
  ;; Returns: T if pass, nil if fail
  (setq lattribs (hcnm-bn-dwg-to-lattribs ename))
  (setq actual-text (cadr (assoc tag lattribs)))
  (setq result (= actual-text expected-text))
  (setq status (if result "PASS" "FAIL"))
  (setq message
    (strcat "Tag: " tag "\n"
            "Expected: \"" expected-text "\"\n"
            "Actual:   \"" (if actual-text actual-text "<<NIL>>") "\""
    )
  )
  (setq location (test-get-bubble-annotation-location ename))
  (if location
    (c:test-annotate-result location status (strcat test-name "\n" message))
  )
  (test-write-report-entry test-name status message)
  result
)
(defun test-validate-xdata (ename tag expected-auto-type test-name /
                           xdata tag-entry composite-pairs first-pair composite-key auto-text result status message location
                          )
  ;; Validate XDATA exists and has correct auto-type
  ;; Args:
  ;;   ename - Entity name of bubble
  ;;   tag - Attribute tag (e.g., "NOTETXT1")
  ;;   expected-auto-type - Expected auto-type (e.g., "Sta", "Dia", "NE")
  ;;   test-name - Name for report
  ;; Returns: T if XDATA found with correct auto-type, nil otherwise
  (setq xdata (hcnm-xdata-read ename))
  ;; xdata format: '(("TAG" . (((auto-type . handle) . auto-text) ...)))
  ;; Check if xdata is an alist and has entry for tag
  (if (and xdata (listp xdata))
    (progn
      (setq tag-entry (assoc tag xdata))
      (if tag-entry
        (progn
          (setq composite-pairs (cdr tag-entry))  ; List of composite pairs
          (if (and composite-pairs (listp composite-pairs))
            (progn
              (setq first-pair (car composite-pairs))  ; ((auto-type . handle) . auto-text)
              (setq composite-key (car first-pair))    ; (auto-type . handle)
              (setq auto-text (cdr first-pair))
            )
            (setq composite-key nil auto-text nil)
          )
        )
        (setq composite-key nil auto-text nil)
      )
    )
    (setq composite-key nil auto-text nil)
  )
  (setq result
    (and xdata
         (assoc tag xdata)
         composite-key
         (equal expected-auto-type (car composite-key))
    )
  )
  (setq status (if result "PASS" "FAIL"))
  (setq message
    (strcat "Tag: " tag "\n"
            "Expected auto-type: \"" expected-auto-type "\"\n"
            "XDATA composite-key: " (vl-prin1-to-string composite-key) "\n"
            "XDATA auto-text: \"" (if auto-text auto-text "<<NIL>>") "\""
    )
  )
  (setq location (test-get-bubble-annotation-location ename))
  (if location
    (c:test-annotate-result location status (strcat test-name " (XDATA)\n" message))
  )
  (test-write-report-entry (strcat test-name " (XDATA)") status message)
  result
)
(defun test-get-bubble-annotation-location (ename / elist pt-insert x y)
  ;; Get insertion point of bubble for annotation placement
  ;; Returns: String "x,y" coordinates offset to right of bubble
  ;; Returns: nil if error occurs
  ;; Use entget DXF code 10 to avoid safearray issues
  (if (and
        (setq elist (entget ename))
        (setq pt-insert (cdr (assoc 10 elist)))
        (numberp (setq x (car pt-insert)))
        (numberp (setq y (cadr pt-insert)))
      )
    (strcat (rtos (+ x 200.0) 2 2) "," (rtos y 2 2))
    nil  ; Return nil on error
  )
)
(defun test-validate-vptrans-removed (ename test-name / vptrans status message location)
  ;; Validate VPTRANS XRECORD does not exist
  ;; Args:
  ;;   ename - Entity name of bubble
  ;;   test-name - Name for report
  ;; Returns: T if correctly removed, nil if still present
  (setq vptrans (hcnm-bn-get-viewport-transform-xdata ename))
  (setq status (if vptrans "FAIL" "PASS"))
  (setq message
    (if vptrans
      (strcat "FAIL: VPTRANS still present after clearing coordinate-based auto-text\n"
              "Data: " (vl-prin1-to-string vptrans) "\n"
              "Action: Manual cleanup required")
      "PASS: VPTRANS correctly removed"
    )
  )
  (setq location (test-get-bubble-annotation-location ename))
  (if location
    (c:test-annotate-result location status (strcat test-name " (VPTRANS Cleanup)\n" message))
  )
  (test-write-report-entry (strcat test-name " (VPTRANS Cleanup)") status message)
  (not vptrans)  ; Return T if removed
)
(defun test-validate-vptrans-created (ename test-name / vptrans status message location)
  ;; Validate VPTRANS XRECORD exists (for paper space coordinate-based auto-text)
  ;; Args:
  ;;   ename - Entity name of bubble
  ;;   test-name - Name for report
  ;; Returns: T if created, nil if missing
  (setq vptrans (hcnm-bn-get-viewport-transform-xdata ename))
  (setq status (if vptrans "PASS" "FAIL"))
  (setq message
    (if vptrans
      (strcat "PASS: VPTRANS created for paper space coordinate-based auto-text\n"
              "Viewport: " (itoa (car vptrans)) "\n"
              "Transform points: " (itoa (length (cdr vptrans))))
      (strcat "FAIL: VPTRANS not created\n"
              "Expected: Viewport transform for paper space auto-text\n"
              "Action: Check hcnm-bn-eb-save VPTRANS creation logic")
    )
  )
  (setq location (test-get-bubble-annotation-location ename))
  (if location
    (c:test-annotate-result location status (strcat test-name " (VPTRANS Created)\n" message))
  )
  (test-write-report-entry (strcat test-name " (VPTRANS Created)") status message)
  vptrans  ; Return T if created
)
;;==============================================================================
;; KEY NOTES TABLE VALIDATION FUNCTIONS
;;==============================================================================
(defun c:test-validate-key-table ( / ss table-ent table-data box1-qty box2-count result-msg)
  ;; Find Key Notes Table blocks (noteqty.dwg insertions)
  ;; CNM builds table from noteqty.dwg block repeated for each note
  (setq ss (ssget "_X" '((0 . "INSERT") (2 . "NOTEQTY*"))))
  (if ss
    (progn
      ;; Extract quantities from table block attributes
      ;; This requires understanding noteqty.dwg attribute structure
      ;; For now, just verify table exists
      (setq result-msg
        (strcat "PASS: Key Notes Table generated\n"
                "  Table blocks found: " (itoa (sslength ss)) "\n"
                "  (Manual verification required for quantities)\n\n"
                "  Expected:\n"
                "    BOX-1: 4146 LF (100+150+75)\n"
                "    BOX-2: 1 EA (count)\n"
                "    CIR-1: 662 LF\n"
                "    CIR-2: 1 EA (count)\n"
                "    DIA-2: 3 EA (count)\n"
                "    HEX-2: 2 EA (count)\n\n"
                "    OCT-1: 640 LF\n"
                "    OCT-2: 1 EA (count)\n\n"
                "    PEN-1: 502 LF\n\n"
                "    REC-1: 456 LF\n\n"
                "  Check: Visual inspection of table\n"
                "  Check: cnm-test-TEST-LAYOUT.not file created"))
      (princ "\nKey Notes Table: Generated")
      (test-write-report-entry "TEST H: Key Notes Table Generation" "PASS" result-msg)
    )
    (progn
      (setq result-msg "FAIL: Key Notes Table NOT generated")
      (princ "\nKey Notes Table: FAIL")
      (test-write-report-entry "TEST H: Key Notes Table Generation" "FAIL" result-msg)
    )
  )
  ;; Additional check: Verify .not file created
  ;; KT made on a layout appends the layout name; c:test-remove-not-files deletes both names before KT
  (cond
    ((findfile (strcat (getvar "dwgprefix") "cnm-test.not"))
     (princ "\nWARNING: .not file has no layout suffix")
     (test-write-report-entry "TEST H: .not File Creation" "FAIL" "KT on TEST-LAYOUT wrote cnm-test.not instead of cnm-test-TEST-LAYOUT.not")
    )
    ((findfile (strcat (getvar "dwgprefix") "cnm-test-TEST-LAYOUT.not"))
     (princ "\n.not file created for QT processing")
     (test-write-report-entry "TEST H: .not File Creation" "PASS" "cnm-test-TEST-LAYOUT.not exists in project folder")
    )
    (t
     (princ "\nWARNING: .not file NOT created")
     (test-write-report-entry "TEST H: .not File Creation" "FAIL" "cnm-test-TEST-LAYOUT.not missing from project folder")
    )
  )
  (princ)
)
(defun c:test-remove-not-files ( / not-name)
  ;; Remove .not files from earlier runs so TEST H sees only this run's KT output
  (foreach
     not-name '("cnm-test.not" "cnm-test-TEST-LAYOUT.not")
    (setq not-name (strcat (getvar "dwgprefix") not-name))
    (if (findfile not-name) (vl-file-delete not-name))
  )
  (princ)
)
;;==============================================================================
;; QUANTITY TAKEOFF TABLE VALIDATION FUNCTIONS
;;==============================================================================
(defun c:test-create-qt-lst-file ( / csv-name)
  ;; Remove last run's QT CSV so test-validate-qt-csv sees only this run's output
  (setq csv-name (strcat (getvar "dwgprefix") "cnm-test.csv"))
  (if (findfile csv-name) (vl-file-delete csv-name))
  ;; Create simple sheet list for single-sheet QT test (KT ran on TEST-LAYOUT)
  (test-write-file "cnm-test.lst" "cnm-test-TEST-LAYOUT")
  (if (findfile (strcat (getvar "dwgprefix") "cnm-test.lst"))
    (progn
      (princ "\nSheet list created: cnm-test.lst")
      (test-write-report-entry "SETUP: Create Sheet List" "PASS" "cnm-test.lst created with single entry: cnm-test-TEST-LAYOUT")
    )
    (progn
      (princ "\nWARNING: Failed to create cnm-test.lst")
      (test-write-report-entry "SETUP: Create Sheet List" "FAIL" "Failed to create cnm-test.lst file")
    )
  )
  (princ)
)
(defun test-write-file (filename contents / f)
  ;; Write string to text file in current drawing folder
  (setq f (open (strcat (getvar "dwgprefix") filename) "w"))
  (if f
    (progn
      (write-line contents f)
      (close f)
      t
    )
    nil
  )
)
(defun c:test-validate-qt-table ( / ss table-text result-msg)
  ;; Find QT table text objects
  ;; CNM QT generates text following current style/dimension settings
  (setq ss (ssget "_X" '((0 . "TEXT,MTEXT"))))
  (if ss
    (progn
      (setq result-msg
        (strcat "PASS: QT Table generated\n"
                "  Text objects found: " (itoa (sslength ss)) "\n"
                "  (Manual verification required for totals)\n\n"
                "  Expected single-sheet totals:\n"
                "    BOX-1: 4146 LF\n"
                "    BOX-2: 1 EA\n"
                "    CIR-1: 662 LF\n"
                "    CIR-2: 1 EA\n"
                "    DIA-2: 3 EA\n"
                "    HEX-2: 2 EA\n\n"
                "    OCT-1: 640 LF\n"
                "    OCT-2: 1 EA\n\n"
                "    PEN-1: 502 LF\n\n"
                "    REC-1: 456 LF\n\n"
                "  Check: Visual inspection of QT table"))
      (princ "\nQT Table: Generated")
      (test-write-report-entry "TEST I: QT Table Generation" "PASS" result-msg)
    )
    (progn
      (setq result-msg "FAIL: QT Table NOT generated (no text objects found)")
      (princ "\nQT Table: FAIL")
      (test-write-report-entry "TEST I: QT Table Generation" "FAIL" result-msg)
    )
  )
  (test-validate-qt-csv)
  (princ)
)
(defun test-validate-qt-csv ( / csv-name data-line f header lst-name missing sheet)
  ;; QT writes <dwgname>.csv with a quantity column per sheet in the .lst
  ;; Header column for a sheet is "<FULL PATH>\<SHEET>.NOT (SINGLE PHASE)" or "... PHASE n"
  (setq
    csv-name (strcat (getvar "dwgprefix") "cnm-test.csv")
    lst-name (strcat (getvar "dwgprefix") "cnm-test.lst")
    missing ""
  )
  (cond
    ((not (findfile csv-name))
     (princ "\nQT CSV: FAIL")
     (test-write-report-entry "TEST I: QT CSV Export" "FAIL" "FAIL: cnm-test.csv was not created")
    )
    (t
     (setq
       f (open csv-name "r")
       header (read-line f)
       data-line (read-line f)
       f (close f)
       f (open lst-name "r")
     )
     (while (setq sheet (read-line f))
       (if (not (wcmatch header (strcat "*\\" (strcase sheet) ".NOT (*")))
         (setq missing (strcat missing " " sheet))
       )
     )
     (setq f (close f))
     (cond
       ((/= missing "")
        (princ "\nQT CSV: FAIL")
        (test-write-report-entry "TEST I: QT CSV Export" "FAIL" (strcat "FAIL: CSV header has no column for sheet(s):" missing "\n  Header: " header))
       )
       ((not data-line)
        (princ "\nQT CSV: FAIL")
        (test-write-report-entry "TEST I: QT CSV Export" "FAIL" (strcat "FAIL: CSV has a header but no rows\n  Header: " header))
       )
       (t
        (princ "\nQT CSV: PASS")
        (test-write-report-entry "TEST I: QT CSV Export" "PASS" (strcat "PASS: cnm-test.csv has a column for every sheet in cnm-test.lst\n  Header: " header))
       )
     )
    )
  )
)
(princ)
;;==============================================================================
;; TEST RUN TIMING & CLEANUP HELPERS
;;==============================================================================
(defun c:test-log-start ( / logfile timestamp f resultsdir)
  ;; Append a START timestamp to test-results/cnm-test-run.log
  ;; Create test-results subfolder if it doesn't exist
  (setq resultsdir (strcat (getvar "dwgprefix") "test-results"))
  (if (not (vl-file-directory-p resultsdir))
    (vl-mkdir resultsdir)
  )
  (setq logfile (strcat resultsdir "\\cnm-test-run.log"))
  (setq timestamp (menucmd "M=$(edtime,$(getvar,date),YYYY-MO-DD HH:MM:SS)"))
  (if (setq f (open logfile "a"))
    (progn
      (write-line (strcat "START: " timestamp) f)
      (close f)
      (princ (strcat "\nTest run start: " timestamp))
    )
    (princ "\nFailed to open test run log for writing")
  )
  (princ)
)
(defun c:test-log-end ( / logfile timestamp f resultsdir)
  ;; Append an END timestamp to test-results/cnm-test-run.log
  (setq resultsdir (strcat (getvar "dwgprefix") "test-results"))
  (setq logfile (strcat resultsdir "\\cnm-test-run.log"))
  (setq timestamp (menucmd "M=$(edtime,$(getvar,date),YYYY-MO-DD HH:MM:SS)"))
  (if (setq f (open logfile "a"))
    (progn
      (write-line (strcat "END:   " timestamp) f)
      (close f)
      (princ (strcat "\nTest run end: " timestamp))
    )
    (princ "\nFailed to open test run log for writing")
  )
  (princ)
)
(defun c:test-cleanup-project-files ( / pfx fd1 fd2 msg)
  ;; Remove temporary project files created by the test run
  ;; cnm.ini: CNM project settings (auto-created from template)
  ;; constnot.csv: Project notes database (auto-created from template)
  ;; cnm-test.csv (QT export) is kept for inspection; c:test-create-qt-lst-file removes it before the next QT
  (setq pfx (getvar "dwgprefix"))
  (setq fd1 (strcat pfx "cnm.ini"))
  (setq fd2 (strcat pfx "constnot.csv"))
  (setq msg "")
;;  (if (and fd1 (findfile fd1)) (vl-file-delete fd1) (setq msg (strcat msg " cnm.ini not found;")))
  (if (and fd2 (findfile fd2)) (vl-file-delete fd2) (setq msg (strcat msg " constnot.csv not found;")))
  (test-write-report-entry "CLEANUP: Project files" "INFO" (strcat "Removed files if present." msg))
  (princ "\nCleanup complete: constnot.csv removed if present")
  (princ)
)
;;==============================================================================
;; BUBBLE TEXT HELPER
;;==============================================================================
(defun test-get-bubble-text (ename-bubble tag / lattribs)
  ;; Get current text value for a bubble tag
  ;; Args:
  ;;   ename-bubble - Entity name of bubble block
  ;;   tag - Attribute tag (e.g., "NOTETXT1")
  ;; Returns: String text value or nil if not found
  (setq lattribs (hcnm-bn-dwg-to-lattribs ename-bubble))
  (cadr (assoc tag lattribs))
)
