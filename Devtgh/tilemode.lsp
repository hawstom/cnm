;Written by Thomas Gail Haws
(defun c:haws-0 ()
  (setvar"regenmode"0)
  (setvar"tilemode"0)
  (if(=(getvar"psltscale")1)(setvar"ltscale"1))
  (setvar"regenmode"1)
  (princ)
)
(defun c:haws-1 ( / ds LT)
  (setvar"regenmode"0)
  (setq ds (HAWS-DWGSCALE)lt (getvar"ltscale"))
  (if(=(getvar"psltscale")1)
    (cond
      ( (and(= ds 1)(/= lt 1))(setvar "tilemode" 1))
      ( (= ds lt 1)
        (initget 1)
        (setq ds(getreal"\nNew value for ltscale: "))
        (setvar "ltscale" ds)
        (setvar "tilemode" 1)
      )
      ( (/= ds 1) (setvar "ltscale" ds)(setvar"tilemode"1))
    )
    (setvar "tilemode" 1)
  )
  (setvar"regenmode"1)
  (princ)
)
