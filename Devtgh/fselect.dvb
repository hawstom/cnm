Attribute VB_Name = "UserFormFileSelect"
Attribute VB_Base = "0{257E5EDC-F086-4FC1-B6FF-771588B41F22}{B3F2DEE1-E496-4611-B7AF-86EA29226B8F}"
Attribute VB_GlobalNameSpace = False
Attribute VB_Creatable = False
Attribute VB_PredeclaredId = True
Attribute VB_Exposed = False
Attribute VB_TemplateDerived = False
Attribute VB_Customizable = False
Option Explicit
Dim blnListChanged As Boolean
Private Sub UserForm_Initialize()
    Call IOFileRead
    Me.ListBox1.List = strFileList
End Sub
Private Sub CommandButtonAdd_Click()
    Dim i As Integer
    'Uses class module CommonDialog to get a list of filenames.
    'Returns a string array of filenames
    Dim cmdlgOpenFile As New clsCommonDialog
    Dim strFileFolderName As String
    Dim strBuff As String
    Dim strFolder As String
    Dim strFile As String
    Dim strPath As String
    Dim File As Variant
    Dim pos As Long
    Dim item As String
    
    cmdlgOpenFile.InitDir = ThisDrawing.GetVariable("dwgprefix")
    cmdlgOpenFile.Filter = strFilespec
    cmdlgOpenFile.Flags = OFN_ALLOWMULTISELECT Or _
    OFN_EXPLORER
    
    Call DisableButtons
    cmdlgOpenFile.ShowOpen
    Call EnableButtons
    
    strFileFolderName = cmdlgOpenFile.FileName
    If strFileFolderName > Chr$(1) Then
        'Get the size of the old array,
        'and set i to trim the last member if it is empty.
        i = (UBound(strFileList))
        If strFileList(i) = "" Then
            i = i - 1
        End If
        
        'Start parsing the browse return string
        pos = InStr(1, strFileFolderName, vbNullChar)
        strFolder = ""
        
        'If there were multiple files selected
        If pos Then
            strFolder = Mid$(strFileFolderName, 1, pos - 1) & "\"
            strFileFolderName = Mid$(strFileFolderName, pos + 1)
            pos = InStrRev(strFileFolderName, vbNullChar, -1, vbTextCompare)
            Do While pos
                AddFileToList strFolder & Mid$(strFileFolderName, pos + 1), i
                strFileFolderName = Mid$(strFileFolderName, 1, pos - 1)
                pos = InStrRev(strFileFolderName, vbNullChar, -1, vbTextCompare)
            Loop
        End If
        blnListChanged = True
        AddFileToList strFolder & strFileFolderName, i
        ListBox1.List = strFileList
    End If
    
End Sub
Private Function StripDelimitedItem(ByRef startStrg As String, _
                                    delimiter As String) As String

  'take a string separated by nulls,
  'split off 1 item, and shorten the string
  'so the next item is ready for removal.
   Dim pos As Long
   Dim item As String
   
   pos = InStr(1, startStrg, delimiter)
   
   If pos Then

      StripDelimitedItem = Mid$(startStrg, 1, pos - 1)
      startStrg = Mid$(startStrg, pos + 1, Len(startStrg))
    
   End If

End Function
Private Sub AddFileToList(strNewFile As String, i As Integer)
    Dim vBoxFile As Variant
    Dim blnNewFile As Boolean
    blnNewFile = True
    For Each vBoxFile In strFileList()
        If vBoxFile = strNewFile Then blnNewFile = False
    Next
    If blnNewFile Then
        i = i + 1
        ReDim Preserve strFileList(0 To i) As String
        strFileList(i) = strNewFile
    End If
End Sub
Private Sub CommandButtonRemove_Click()
    Dim iListIndex As Integer
    Dim iListBox As Integer
    Dim iTempFileList As Integer
    Dim vFile As Variant
    Dim strTempFileList() As String
    Dim strItem As String
  
    iTempFileList = 0
    'Put a dummy element in strTempFileList since I don't know how
    'to check whether it has any elements.
    ReDim strTempFileList(0)
    iListIndex = UBound(strFileList)
    'Step through list displayed
    For iListBox = 0 To ListBox1.ListCount - 1
        'If this file isn't selected for removal
        If ListBox1.Selected(iListBox) = False Then
          'Increase the size of the temp list and
          ReDim Preserve strTempFileList(iTempFileList)
          'Put this file into the temp list
          strTempFileList(iTempFileList) = strFileList(iListBox)
          'Also note where the next file will go in the temp list
          iTempFileList = iTempFileList + 1
        Else
          'If this file is selected for removal, mark this position to be selected when finished.
          iListIndex = iTempFileList
          'and note that there were changes
          blnListChanged = True
        End If
    Next
    'If there were files not marked for removal they are in temp list
    If strTempFileList(0) > "" Then
        'Move them to the permanent list
        ReDim strFileList(UBound(strTempFileList))
        For iTempFileList = 0 To UBound(strTempFileList)
            strFileList(iTempFileList) = strTempFileList(iTempFileList)
        Next
        'And put them in the list box
        ListBox1.List = strFileList
        'If the marker for final selection was higher than the length of the list, mark the last file
        If iListIndex > UBound(strFileList) Then iListIndex = UBound(strFileList)
        ListBox1.Selected(iListIndex) = True
        ListBox1.ListIndex = iListIndex
        
    Else
        ReDim strFileList(0)
        ListBox1.Clear
    End If
End Sub
Private Sub CommandButtonMoveUp_Click() 'Move up
    Dim iListBox As Integer
    Dim iTempFileList As Integer
    Dim iOffset As Integer
    Dim strTempFileList() As String
    Dim blnTempFileList() As Boolean
    
    ReDim strTempFileList(UBound(strFileList)) As String
    ReDim blnTempFileList(UBound(strFileList)) As Boolean
'Run through the items from 0 to end
'If an item is selected,
'Lower its index by one and note that list changed if that index is within bounds
'and "" in the new list.
'Else put straight into the new list.
    For iListBox = 0 To ListBox1.ListCount - 1
        If ListBox1.Selected(iListBox) = True Then
            If iListBox > 0 Then
                If strTempFileList(iListBox - 1) = "" Then
                    strTempFileList(iListBox - 1) = strFileList(iListBox)
                    blnTempFileList(iListBox - 1) = True
                    blnListChanged = True
                Else
                    strTempFileList(iListBox) = strFileList(iListBox)
                    blnTempFileList(iListBox) = True
                End If
            Else
                    strTempFileList(iListBox) = strFileList(iListBox)
                    blnTempFileList(iListBox) = True
            End If
        End If
    Next
'Run through again
'If an item is not selected,
'put it into the first available position in the new list.
    For iListBox = 0 To ListBox1.ListCount - 1
        If ListBox1.Selected(iListBox) = False Then
            iOffset = 0
            Do Until strTempFileList(iListBox + iOffset) = ""
                iOffset = iOffset + 1
            Loop
            strTempFileList(iListBox + iOffset) = strFileList(iListBox)
            blnTempFileList(iListBox + iOffset) = False
        End If
    Next
    For iTempFileList = 0 To UBound(strTempFileList)
        strFileList(iTempFileList) = strTempFileList(iTempFileList)
    Next
    ListBox1.List = strFileList
    For iTempFileList = 0 To UBound(strTempFileList)
        If blnTempFileList(iTempFileList) = True Then
            ListBox1.Selected(iTempFileList) = True
            ListBox1.ListIndex = iTempFileList
        End If
    Next
End Sub
Private Sub CommandButtonMoveDown_Click()
    Dim iListBox As Integer
    Dim iTempFileList As Integer
    Dim iOffset As Integer
    Dim strTempFileList() As String
    Dim blnTempFileList() As Boolean
    
    ReDim strTempFileList(UBound(strFileList)) As String
    ReDim blnTempFileList(UBound(strFileList)) As Boolean
'Run through the items from 0 to end
'If an item is selected,
'Raise its index by one and note that list has changed if that index is within bounds
'and "" in the new list.
'Else put straight into the new list.
    For iListBox = ListBox1.ListCount - 1 To 0 Step -1
        If ListBox1.Selected(iListBox) = True Then
            If iListBox < ListBox1.ListCount - 1 Then
                If strTempFileList(iListBox + 1) = "" Then
                    strTempFileList(iListBox + 1) = strFileList(iListBox)
                    blnTempFileList(iListBox + 1) = True
                    blnListChanged = True
                Else
                    strTempFileList(iListBox) = strFileList(iListBox)
                    blnTempFileList(iListBox) = True
                End If
            Else
                    strTempFileList(iListBox) = strFileList(iListBox)
                    blnTempFileList(iListBox) = True
            End If
        End If
    Next
'Run through again
'If an item is not selected,
'put it into the first available position in the new list.
    For iListBox = ListBox1.ListCount - 1 To 0 Step -1
        If ListBox1.Selected(iListBox) = False Then
            iOffset = 0
            Do Until strTempFileList(iListBox - iOffset) = ""
                iOffset = iOffset + 1
            Loop
            strTempFileList(iListBox - iOffset) = strFileList(iListBox)
            blnTempFileList(iListBox - iOffset) = False
        End If
    Next
    For iTempFileList = 0 To UBound(strTempFileList)
        strFileList(iTempFileList) = strTempFileList(iTempFileList)
    Next
    ListBox1.List = strFileList
    For iTempFileList = 0 To UBound(strTempFileList)
        If blnTempFileList(iTempFileList) = True Then
            ListBox1.Selected(iTempFileList) = True
            ListBox1.ListIndex = iTempFileList
'            ListBox1.TopIndex = iTempFileList
        End If
    Next
End Sub
Private Sub CommandButtonSortPlus_Click()
    Dim blnSorted As Boolean
    Dim iFile As Integer
    Dim iFileAhead As Integer
    Dim strTempHolder As String
    Dim blnTempFileList() As Boolean
    
    ReDim blnTempFileList(UBound(strFileList)) As Boolean
    
'   Remember what was selected
    For iFile = LBound(strFileList) To UBound(strFileList)
        If ListBox1.Selected(iFile) = True Then
            blnTempFileList(iFile) = True
        End If
    Next iFile
    
    blnSorted = False
    Do While blnSorted = False
        blnSorted = True
        For iFile = LBound(strFileList) To UBound(strFileList) - 1
            If ListBox1.Selected(iFile) = True Then
                For iFileAhead = iFile + 1 To UBound(strFileList)
                    If UCase(strFileList(iFile)) > UCase(strFileList(iFileAhead)) _
                    And ListBox1.Selected(iFileAhead) = True Then
                        strTempHolder = strFileList(iFile)
                        strFileList(iFile) = strFileList(iFileAhead)
                        strFileList(iFileAhead) = strTempHolder
                        blnSorted = False
                    End If
                Next iFileAhead
            End If
        Next iFile
    Loop
    ListBox1.List = strFileList
    For iFile = 0 To UBound(strFileList)
        If blnTempFileList(iFile) = True Then
            ListBox1.Selected(iFile) = True
            ListBox1.ListIndex = iFile
'            ListBox1.TopIndex = iTempFileList
        End If
    Next
    blnListChanged = True
End Sub
Private Sub CommandButtonSortMinus_Click()
    Dim blnSorted As Boolean
    Dim iFile As Integer
    Dim iFileAhead As Integer
    Dim strTempHolder As String
    Dim blnTempFileList() As Boolean
    
    ReDim blnTempFileList(UBound(strFileList)) As Boolean

'   Remember what was selected
    For iFile = LBound(strFileList) To UBound(strFileList)
        If ListBox1.Selected(iFile) = True Then
            blnTempFileList(iFile) = True
        End If
    Next iFile
    
    blnSorted = False
    Do While blnSorted = False
        blnSorted = True
        For iFile = LBound(strFileList) To UBound(strFileList) - 1
            If ListBox1.Selected(iFile) = True Then
                For iFileAhead = iFile + 1 To UBound(strFileList)
                    If UCase(strFileList(iFile)) < UCase(strFileList(iFileAhead)) _
                    And ListBox1.Selected(iFileAhead) = True Then
                        strTempHolder = strFileList(iFile)
                        strFileList(iFile) = strFileList(iFileAhead)
                        strFileList(iFileAhead) = strTempHolder
                        blnSorted = False
                    End If
                Next iFileAhead
            End If
        Next iFile
    Loop
    ListBox1.List = strFileList
    For iFile = 0 To UBound(strFileList)
        If blnTempFileList(iFile) = True Then
            ListBox1.Selected(iFile) = True
            ListBox1.ListIndex = iFile
'            ListBox1.TopIndex = iTempFileList
        End If
    Next
    blnListChanged = True
End Sub
Private Sub CommandButtonNew_Click()
    Dim i As Integer
    'Uses class module CommonDialog to get a list of filenames.
    'Returns a string array of filenames
    Dim cmdlgOpenFile As New clsCommonDialog
    Dim File As Variant
    Dim iMsgBoxResponse As Integer
    
    If blnListChanged = True Then
        iMsgBoxResponse = MsgBox("List has changed." & vbCrLf & _
        "Do you want to save this list first?", _
        vbYesNoCancel, "List not saved")
    End If
    If iMsgBoxResponse = vbYes Then Call IOFileSave
    If iMsgBoxResponse = vbCancel Then GoTo EndSub
    cmdlgOpenFile.InitDir = ThisDrawing.GetVariable("dwgprefix")
    cmdlgOpenFile.Filter = "List Files (*.lst)|*.lst"
    cmdlgOpenFile.Flags = OFN_OVERWRITEPROMPT
    
    Call DisableButtons
    cmdlgOpenFile.ShowSave
    Call EnableButtons
    
    strIOFileNameTemp = cmdlgOpenFile.FileName
    'If a file name was provided by the user then
    'all the following, else nothing.
    If strIOFileNameTemp > Chr$(1) Then
        strIOFileName = strIOFileNameTemp
        ListBox1.Clear
        ReDim strFileList(0 To 0) As String
        Me.Caption = "Files to include - [" & strIOFileName & "]"
    End If
EndSub:
End Sub
Private Sub CommandButtonOpen_Click()
    Dim i As Integer
    'Uses class module CommonDialog to get a list of filenames.
    'Returns a string array of filenames
    Dim cmdlgOpenFile As New clsCommonDialog
    Dim File As Variant
    Dim iMsgBoxResponse As Integer
    
    If blnListChanged = True Then
        iMsgBoxResponse = MsgBox("List has changed." & vbCrLf & _
        "Do you want to save this list first?", _
        vbYesNoCancel, "List not saved")
    End If
    If iMsgBoxResponse = vbYes Then Call IOFileSave
    If iMsgBoxResponse = vbCancel Then GoTo EndSub
    cmdlgOpenFile.InitDir = ThisDrawing.GetVariable("dwgprefix")
    cmdlgOpenFile.Filter = "List Files (*.lst)|*.lst"
    cmdlgOpenFile.Flags = OFN_FILEMUSTEXIST
    
    Call DisableButtons
    cmdlgOpenFile.ShowOpen
    Call EnableButtons
    
    strIOFileNameTemp = cmdlgOpenFile.FileName
    'If a file name was provided by the user then
    'all the following, else nothing.
    If strIOFileNameTemp > Chr$(1) Then
        strIOFileName = strIOFileNameTemp
        Call IOFileRead
        ListBox1.List = strFileList
        Me.Caption = "Files to include - [" & strIOFileName & "]"
    End If
EndSub:
End Sub
Private Sub CommandButtonSave_Click()
    Call IOFileSave
End Sub
Private Sub CommandButtonSaveAs_Click()
    Dim i As Integer
    'Uses class module CommonDialog to show a save dialog box.
    'Returns a file name
    Dim cmdlgOpenFile As New clsCommonDialog
    Dim File As Variant
    
    cmdlgOpenFile.InitDir = ThisDrawing.GetVariable("dwgprefix")
    cmdlgOpenFile.Filter = "List Files (*.lst)|*.lst"
    cmdlgOpenFile.Flags = OFN_OVERWRITEPROMPT Or OFN_PATHMUSTEXIST
    cmdlgOpenFile.DefaultExt = ".lst"
    cmdlgOpenFile.FileName = strIOFileName & Chr(0) & Chr(0)
    
    Call DisableButtons
    cmdlgOpenFile.ShowSave
    Call EnableButtons
    
    strIOFileNameTemp = cmdlgOpenFile.FileName
    'If a file name was provided by the user then
    'all the following, else nothing.
    If strIOFileNameTemp > Chr$(1) Then
        strIOFileName = strIOFileNameTemp
        Call IOFileSave
        Me.Caption = "Files to include - [" & strIOFileName & "]"
    End If
End Sub
Private Sub CommandButtonOK_Click()
    Call IOFileSave
    'The intent below is that calling apps can check for OK and fail if not.
    AutoCAD.Application.ActiveDocument.SetVariable "users2", "OK"
    Unload Me
End Sub
Private Sub CommandButtonCancel_Click()
    Unload Me
End Sub
Private Sub UserForm_Terminate()
    Dim iMsgBoxResponse As Integer
    
    If blnListChanged = True Then
        iMsgBoxResponse = MsgBox("List has changed." & vbCrLf & _
        "Do you want to save this list first?", _
        vbYesNo, "List not saved")
    End If
    If iMsgBoxResponse = vbYes Then Call IOFileSave
End Sub
Private Sub DisableButtons()
    CommandButtonAdd.Enabled = False
    CommandButtonRemove.Enabled = False
    CommandButtonMoveUp.Enabled = False
    CommandButtonMoveDown.Enabled = False
    CommandButtonSortPlus.Enabled = False
    CommandButtonSortMinus.Enabled = False
    CommandButtonNew.Enabled = False
    CommandButtonOpen.Enabled = False
    CommandButtonSave.Enabled = False
    CommandButtonSaveAs.Enabled = False
    CommandButtonOK.Enabled = False
    CommandButtonCancel.Enabled = False
End Sub
Private Sub EnableButtons()
    CommandButtonAdd.Enabled = True
    CommandButtonRemove.Enabled = True
    CommandButtonMoveUp.Enabled = True
    CommandButtonMoveDown.Enabled = True
    CommandButtonSortPlus.Enabled = True
    CommandButtonSortMinus.Enabled = True
    CommandButtonNew.Enabled = True
    CommandButtonOpen.Enabled = True
    CommandButtonSave.Enabled = True
    CommandButtonSaveAs.Enabled = True
    CommandButtonOK.Enabled = True
    CommandButtonCancel.Enabled = True
End Sub
Private Sub IOFileRead()
    Dim iInFile As Integer
    Dim iValidFile As Integer
    Dim strFileLine As String
    Dim vFile As Variant
    Dim blnDifferentExtensions As Boolean
    
    ReDim strFileList(0 To 0) As String
    
'Add extension to old-style names in list file.
    
    iInFile = FreeFile(0)
    iValidFile = 0
    strExtension = Mid(strFilespec, InStrRev(strFilespec, ".", -1, vbTextCompare))
    On Error GoTo NewList
    Open strIOFileName For Input Shared As iInFile
        Do While Not EOF(iInFile)
            Line Input #iInFile, strFileLine
            'Add default extension if listed file doesn't have it.
            If Left(Right(strFileLine, Len(strExtension)), 1) <> "." Then
                strFileLine = strFileLine & strExtension
                blnListChanged = True
            End If
            'Flag user warning if extension isn't default.
            If LCase(Right(strFileLine, Len(strExtension))) <> LCase(strExtension) Then
                blnDifferentExtensions = True
            End If
            'If line gives a file that is found containing compatible data, add it to array.
            On Error GoTo NextFile
            If Dir(strFileLine) <> "" Then
                ReDim Preserve strFileList(0 To iValidFile) As String
                strFileList(iValidFile) = strFileLine
                iValidFile = iValidFile + 1
            Else
                blnListChanged = True
            End If
NextFile:
        Loop
    Close iInFile
NewList:
    Close iInFile
    If blnDifferentExtensions Then
        MsgBox "The selected file doesn't seem to be a list of files for this application." & vbCrLf & "This may cause the current application to fail.", vbExclamation, "Wrong List Type"
    End If
    If blnListChanged = True Then
        MsgBox "The file " & strIOFileName & vbCrLf & "has been converted to a list usable by this application." & vbCrLf & "You must save the modified contents to a new file." & vbCrLf & "Click OK to continue.", vbExclamation, "File Contents Changed"
        Call CommandButtonSaveAs_Click
    End If
End Sub
Private Sub IOFileSave()
    Dim iOutFile As Integer
    Dim vFile As Variant
        
    iOutFile = FreeFile(0)
    Open strIOFileName For Output Shared As iOutFile
    For Each vFile In strFileList
    Print #iOutFile, vFile
    Next
    Close iOutFile
    blnListChanged = False
End Sub

Attribute VB_Name = "clsCommonDialog"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False



' COMMONDIALOG.CLS v1.2 (Last updated 6/15/2000)
' Copyright 2000 by Frank Oquendo
'
' Permission to use, copy, modify, and distribute this software
' for any purpose and without fee is hereby granted, provided
' that the above copyright notice appears in all copies and
' that both that copyright notice and the limited warranty and
' restricted rights notice below appear in all supporting
' documentation.
'
' FRANK OQUENDO (THE AUTHOR) PROVIDES THIS PROGRAM "AS IS" AND WITH
' ALL FAULTS. THE AUTHOR SPECIFICALLY DISCLAIMS ANY IMPLIED WARRANTY
' OF MERCHANTABILITY OR FITNESS FOR A PARTICULAR USE.  THE AUTHOR
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
' CommonDialog.cls allows developers to access the Windows Open, Save
' and Browse For Folder dialogs without the need for an OCX.
'
' Notes:
' All code for this class module is publicly available througout various posts
' at news://discussion.autodesk.com/autodesk.autocad.customization.vba as well
' as http://msdn.microsoft.com. I do not claim copyright or authorship on code
' presented in these posts, only on this compilation of that code.
'
' Dependencies:
' Use of this class module requires the following files:
' 1. shell32.dll  (SHBrowseForFolder)
' 2. comdlg32.dll (GetOpenFileName and GetSaveFileName)

Option Explicit

Private Declare Function GetOpenFileName Lib "comdlg32.dll" Alias "GetOpenFileNameA" _
    (pOpenfilename As OPENFILENAME) As Long
    
Private Declare Function GetSaveFileName Lib "comdlg32.dll" Alias "GetSaveFileNameA" _
    (pOpenfilename As OPENFILENAME) As Long
    
Private Declare Function SHBrowseForFolder Lib "shell32.dll" Alias "SHBrowseForFolderA" _
    (lpBrowseInfo As BROWSEINFO) As Long
    
Private Declare Function SHGetPathFromIDList Lib "shell32.dll" Alias "SHGetPathFromIDListA" _
    (ByVal pidl As Long, _
     ByVal pszPath As String) As Long

Private Declare Sub CoTaskMemFree Lib "ole32.dll" _
    (ByVal pv As Long)
    
Private Declare Function CommDlgExtendedError Lib "comdlg32.dll" () As Long
    
Private Type OPENFILENAME
        lStructSize As Long
        hwndOwner As Long
        hInstance As Long
        lpstrFilter As String
        lpstrCustomFilter As String
        nMaxCustFilter As Long
        nFilterIndex As Long
        lpstrFile As String
        nMaxFile As Long
        lpstrFileTitle As String
        nMaxFileTitle As Long
        lpstrInitialDir As String
        lpstrTitle As String
        Flags As Long
        nFileOffset As Integer
        nFileExtension As Integer
        lpstrDefExt As String
        lCustData As Long
        lpfnHook As Long
        lpTemplateName As String
End Type

Private Type BROWSEINFO
    hOwner As Long
    pidlRoot As Long
    pszDisplayName As String
    lpszTitle As String
    ulFlags As Long
    lpfn As Long
    lParam As Long
    iImage As Long
End Type

Private Const ERROR_SUCCESS As Long = 0
Private Const MAX_PATH As Long = 260
Private Const BIF_RETURNONLYFSDIRS As Long = &H1

Private mvarPath As String
Private mvarInitDir As String
Private mvarDialogTitle As String
Private mvarFilter As String
Private mvarUserFilter As String
Private mvarDefaultExt As String
Private mvarFileName As String
Private mvarFileTitle As String
Private mvarFilterIndex As Integer
Private mvarFlags As Long
Private mvarMaxFileSize As Integer
Private mvarErrorCode As Long
Private mvarErrorDescription As String



Private Sub Class_Initialize()

    mvarMaxFileSize = 2048
    mvarFileName = String(mvarMaxFileSize, 0)

End Sub


Public Property Let InitDir(newVal As String)

    mvarInitDir = newVal

End Property


Public Property Get InitDir() As String

    InitDir = mvarInitDir

End Property


Public Property Let DialogTitle(ByVal newVal As String)

    mvarDialogTitle = newVal

End Property


Public Property Get DialogTitle() As String

    DialogTitle = mvarDialogTitle

End Property


Public Property Let Filter(ByVal newVal As String)
    
    Dim tmp, i As Integer
    
    tmp = Split(newVal, "|")
    mvarFilter = ""
    mvarUserFilter = newVal
    
    For i = LBound(tmp) To UBound(tmp)
        mvarFilter = mvarFilter & tmp(i) & Chr(0)
    Next
    
    mvarFilter = mvarFilter & Chr(0)

End Property


Public Property Get Filter() As String

    Filter = mvarUserFilter

End Property


Public Property Get Path() As String

    Path = mvarPath

End Property


Public Property Get DefaultExt() As String

    DefaultExt = mvarDefaultExt

End Property


Public Property Let DefaultExt(ByVal newVal As String)

    mvarDefaultExt = newVal

End Property


Public Property Let FileName(ByVal newVal As String)

    mvarFileName = newVal

End Property


Public Property Get FileName() As String

    FileName = mvarFileName

End Property


Public Property Get FileTitle() As String

    FileTitle = mvarFileTitle

End Property


Public Property Let FilterIndex(ByVal newVal As Integer)

    mvarFilterIndex = newVal

End Property


Public Property Get FilterIndex() As Integer

    FilterIndex = mvarFilterIndex

End Property


Public Property Let Flags(ByVal newVal)

    mvarFlags = newVal

End Property


Public Property Get Flags()
    Flags = mvarFlags

End Property


Public Property Let MaxFileSize(ByVal newVal As Integer)

    mvarMaxFileSize = newVal
    mvarFileName = String(newVal, 0)
    
End Property


Public Property Get MaxFileSize() As Integer

    MaxFileSize = mvarMaxFileSize

End Property


Public Property Get LastError()

    LastError = mvarErrorCode

End Property


Public Function Browse() As Long

    ' Displays the Browse For Folder dialog
    Dim Path As String * MAX_PATH
    Dim retval As Long, bi As BROWSEINFO
    
    bi.ulFlags = BIF_RETURNONLYFSDIRS
    bi.lpszTitle = mvarDialogTitle
    retval = SHBrowseForFolder(bi)
    If retval Then
        Call SHGetPathFromIDList(retval, Path)
        mvarPath = Left(Path, InStr(Path, Chr(0)))
    End If
    Call CoTaskMemFree(retval)
    Browse = retval

End Function


Public Function ShowOpen() As Long

    ' Displays the Open dialog.
    ' A positive return value indicates success (the user selected a file)
    ' A zero return indicates the user either cancelled or closed the dialog
    ' A negative return value indicates the API call failed
    
    Dim retval As Long, ofn As OPENFILENAME
    
    With ofn
        .lStructSize = Len(ofn)
        .Flags = mvarFlags
        .lpstrDefExt = mvarDefaultExt
        .lpstrFile = mvarFileName
        .lpstrInitialDir = mvarInitDir
        .lpstrTitle = mvarDialogTitle
        .lpstrFilter = mvarFilter
        .nFilterIndex = mvarFilterIndex
        .lpstrFileTitle = mvarFileName
        .nMaxFile = mvarMaxFileSize
        .nMaxFileTitle = mvarMaxFileSize
    End With
    
    retval = GetOpenFileName(ofn)
    If retval > 0 Then
        Call GetComponents(ofn)
    Else
        mvarErrorCode = CommDlgExtendedError
    End If
    ShowOpen = retval

End Function


Public Function ShowSave() As Long
    
    ' Displays the Save/SaveAs dialog.
    ' A positive return value indicates success (the user selected a file)
    ' A zero return indicates the user either cancelled or closed the dialog
    ' A negative return value indicates the API call failed

    Dim retval As Long, ofn As OPENFILENAME
    
    With ofn
        .lStructSize = Len(ofn)
        .Flags = mvarFlags
        .lpstrDefExt = mvarDefaultExt
        .lpstrFile = mvarFileName
        .lpstrInitialDir = mvarInitDir
        .lpstrTitle = mvarDialogTitle
        .lpstrFilter = mvarFilter
        .nFilterIndex = mvarFilterIndex
        .lpstrFileTitle = mvarFileName
        .nMaxFile = mvarMaxFileSize
        .nMaxFileTitle = mvarMaxFileSize
    End With
    
    retval = GetSaveFileName(ofn)
    If retval > 0 Then
        Call GetComponents(ofn)
    Else
        mvarErrorCode = CommDlgExtendedError
    End If
    ShowSave = retval

End Function


Public Function ParseFileNames() As Variant

    Dim tmp, retval(), i As Integer
    Dim min As Integer, max As Integer
    
    tmp = Split(mvarFileName, Chr(0))
    min = LBound(tmp): max = UBound(tmp)
    
    If min = max Then
    
        ReDim retval(min To min)
        retval(min) = mvarFileName
        
    Else
    
        ReDim retval(min To max - 1)
        
        For i = min To max - 1
            retval(i) = tmp(min) & "\" & tmp(i + 1)
        Next
    
    End If
    
    ParseFileNames = retval

End Function

Private Sub GetComponents(ofn As OPENFILENAME)

    mvarFileName = Left$(ofn.lpstrFile, _
                         InStr(ofn.nFileOffset + 1, _
                               ofn.lpstrFile, _
                               Chr(0) & Chr(0), _
                               vbBinaryCompare) - 1 _
                               )
    mvarFileTitle = Left$(ofn.lpstrFileTitle, InStr(ofn.lpstrFileTitle, Chr(0) & Chr(0)) - 1)
    mvarPath = Left(mvarFileName, ofn.nFileOffset)

End Sub


Private Function Split(ByVal Str As String, ByVal Delim As String) As Variant

    Dim tokens() As String, pos As Long, i As Integer

    pos = InStr(1, Str, Delim, vbTextCompare)
    i = 0

    Do While pos > 0
      ReDim Preserve tokens(0 To i)
      tokens(i) = Mid$(Str, 1, pos - 1)
      If tokens(i) = Delim Then tokens(i) = ""
      Str = Mid$(Str, pos + Len(Delim))
      i = i + 1
      pos = InStr(1, Str, Delim, vbTextCompare)
    Loop

    If Len(Str) > 0 Then
      ReDim Preserve tokens(0 To i)
      tokens(i) = Str
    End If

    Split = tokens

End Function

Attribute VB_Name = "modCommonDialog"
Option Explicit

Public Const OFN_ALLOWMULTISELECT = &H200
Public Const OFN_CREATEPROMPT = &H2000
Public Const OFN_ENABLEHOOK = &H20
Public Const OFN_ENABLETEMPLATE = &H40
Public Const OFN_ENABLETEMPLATEHANDLE = &H80
Public Const OFN_EXPLORER = &H80000
Public Const OFN_EXTENSIONDIFFERENT = &H400
Public Const OFN_FILEMUSTEXIST = &H1000
Public Const OFN_HIDEREADONLY = &H4
Public Const OFN_LONGNAMES = &H200000
Public Const OFN_NOCHANGEDIR = &H8
Public Const OFN_NODEREFERENCELINKS = &H100000
Public Const OFN_NOLONGNAMES = &H40000
Public Const OFN_NONETWORKBUTTON = &H20000
Public Const OFN_NOREADONLYRETURN = &H8000
Public Const OFN_NOTESTFILECREATE = &H10000
Public Const OFN_NOVALIDATE = &H100
Public Const OFN_OVERWRITEPROMPT = &H2
Public Const OFN_PATHMUSTEXIST = &H800
Public Const OFN_READONLY = &H1
Public Const OFN_SHAREAWARE = &H4000
Public Const OFN_SHAREFALLTHROUGH = 2
Public Const OFN_SHARENOWARN = 1
Public Const OFN_SHAREWARN = 0
Public Const OFN_SHOWHELP = &H10
Public Const CDERR_DIALOGFAILURE = &HFFFF
Public Const CDERR_FINDRESFAILURE = &H6
Public Const CDERR_GENERALCODES = &H0
Public Const CDERR_INITIALIZATION = &H2
Public Const CDERR_LOADRESFAILURE = &H7
Public Const CDERR_LOADSTRFAILURE = &H5
Public Const CDERR_LOCKRESFAILURE = &H8
Public Const CDERR_MEMALLOCFAILURE = &H9
Public Const CDERR_MEMLOCKFAILURE = &HA
Public Const CDERR_NOHINSTANCE = &H4
Public Const CDERR_NOHOOK = &HB
Public Const CDERR_NOTEMPLATE = &H3
Public Const CDERR_REGISTERMSGFAIL = &HC
Public Const CDERR_STRUCTSIZE = &H1

Attribute VB_Name = "modFileSelect"
Option Explicit
Public strIOFileName As String
Public strFilespec As String
Public strExtension As String
Public strFileList() As String
Public strIOFileNameTemp As String

'Requires AutoCAD setvar/getvars
'users1 = initial list file name
'users2 = WINAPI Common Dialog filespec
'users3 = Label for top of box
'users4 = User tip for bottom of box
Sub FileSelect()
    Dim objThisDrawing As AcadDocument
    Dim strLabelTop As String
    Dim strLabelTip As String
        
    Set objThisDrawing = AutoCAD.Application.ActiveDocument
    strIOFileName = objThisDrawing.GetVariable("users1")
    strFilespec = objThisDrawing.GetVariable("users2")
    strLabelTop = objThisDrawing.GetVariable("users3")
    strLabelTip = objThisDrawing.GetVariable("users4")
    
    Dim frmFileSelect As UserFormFileSelect
    Set frmFileSelect = New UserFormFileSelect
    frmFileSelect.Caption = "Files to include - [" & strIOFileName & "]"
    frmFileSelect.LabelTop.Caption = strLabelTop
    frmFileSelect.FrameTip.LabelTip.Caption = strLabelTip
    frmFileSelect.Show
    Set frmFileSelect = Nothing
    objThisDrawing.SetVariable "users1", strIOFileName
End Sub
