;Written by Thomas Gail Haws
(defun c:haws-berm ( / dbvar dbold)
  (haws-core-init 165)
  (HAWS-VSAVE '("clayer"))
  (HAWS-MKLAYR "BERM")
  (cond
    ((not (tblsearch "DIMSTYLE" "BERM"))
     (vl-cmdf "._insert" "berm")(vl-cmdf)
     (vl-cmdf "._dim" "_dimblk" "berm")
     (if (getvar "dimldrblk")(vl-cmdf "dimldrblk" "berm"))
     (vl-cmdf "_save" "berm" "_exit")
		)
  )
  (vl-cmdf "_dim1" "_restore" "berm")
  (prompt "\nTop of berm: ")
  (vl-cmdf "._Leader" pause)
  (prompt "\nBottom of berm: ")
  (vl-cmdf pause "" "" "_n")
  (HAWS-VRSTOR)(haws-core-restore)(princ)
)
