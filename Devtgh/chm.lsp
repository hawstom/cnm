(defun c:haws-CHM (/ SS DC DL DLT EC)
(haws-core-init 172)
  (prompt "Pick entities to change: ")
  (setq SS (ssget)
    EC (entsel "Entity to match: ")       DC (cdr (assoc 62 (entget(car EC))))
    DL (cdr (assoc 8 (entget (car EC))))  DLT (cdr (assoc 6 (entget(car EC))))
  )
  (if (not DLT)(setq DLT "BYLAYER"))
  (if (not DC)(setq DC "BYLAYER"))
  (vl-cmdf "._CHANGE" SS "" "_P" "_LT" DLT "_LA" DL "_C" DC "" )
  (prompt "Entities changed to:.....\n ")
  (LIST "Layer:..>>" DL "Color:..>>" DC "Ltype:..>>" DLT)
)
