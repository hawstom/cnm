;Used to edit the length of a selected line. A positive or negative length
;can be added to the line or user can input a new length. The end closest to
;the pick point is edited.
;Rev. 1997 TGH and MKM, AGRA
(defun c:haws-LE () (if (<= 14.0 (atof (getvar "acadver"))) (command "._lengthen")(c:haws-linedit))(princ))
(defun c:haws-LINEDIT (/ pt1 pt2 ten el elev cp olen flag add np)
  (HAWS-ERDF$@ 0)
  (setvar "cmdecho" 0)
  (HAWS-VSAVE '("ucsfollow"))
  (setvar "UCSFOLLOW" 0)
  (setq
    es (HAWS-SELCEROB "\nSelect a LINE to edit: " "LINE")
    enm (car es) el (entget enm) pp (trans (cadr es) 1 enm)
  )
  (redraw enm 3)
  (setq
    pt1 (trans (cdr(assoc 10 el)) 0 1)  pt2 (trans (cdr(assoc 11 el)) 0 1)
    ucsp T
  )
  (command ".UCS" "E" es)
  (setq ten (assoc 10 el)
    elev (assoc 11 el)
    pt1 (trans (HAWS-DXF 10 el) 0 1)
    pt2 (trans (HAWS-DXF 11 el) 0 1)
  )
  (if (< (distance pp pt1) (distance pp pt2))
    (setq cp pt1 flag 10)
    (setq cp pt2 flag 11)
  )
  (setq olen (distance pt1 pt2))
  (princ (strcat "\nLine length: " (rtos olen)))
  (initget 2)
  (setq add (getdist "\nEnter LENGTH to add <return for new length>: "))
  (if (= add nil)
    (progn
      (initget 3)
      (setq add (getdist "\nNew line length: ")
      np (if (= flag 10) (polar pt2 PI add) (polar pt1 PI add)))
    )
    (setq np (polar cp (if (= flag 10) PI 0) add))
  )
  (setq np (trans np 1 enm))
  (if (= flag 10)
    (setq el (subst (cons 10 np) ten el))
    (setq el (subst (cons 11 np) elev el))
  )
  (entmod el)
  (command ".UCS" "P")
  (setq ucsp nil)
  (HAWS-VRSTOR)
  (HAWS-ERRRST)
  (princ)
);end LE
