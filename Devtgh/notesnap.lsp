(defun c:haws-ns ()
  (initget 1 "0 30 45 60")
  (setq notang (getkword "\nSnap angle <0/30/45/60>: "))
  (cond
    ( (wcmatch notang "30,60")
      (command "snap" "s" "i" "" "snap""of" "isoplane" "t")
    )
    (t(command "snap" "s" "s" "" "snap""of" "isoplane" "t"))
  )
  (cond
    ( (wcmatch notang "0,30")(command "snapang" 0))
    ( (wcmatch notang "45")(command "snapang" 45))
    ( (wcmatch notang "60")(command "snapang" 90))
  )
  (princ)
)
